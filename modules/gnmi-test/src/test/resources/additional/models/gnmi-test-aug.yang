module gnmi-test-aug {

  yang-version "1";
  namespace "test:aug";
  prefix "gta";

  import openconfig-extensions { prefix oc-ext; }
  import gnmi-test-model {prefix gtm;}

  oc-ext:openconfig-version "1.0.0";

  augment /gtm:test-data {
    leaf interface {
      type string;
    }
  }

  augment "/gtm:test-data/gtm:nested-container" {
    list interface {
      key "name";
      description
        "The list of named interfaces on the device.";
      leaf name {
        type string;
      }
      container config {
        leaf name {
          type string;
        }
        leaf type {
          type string;
        }
        leaf mtu {
          type uint16;
        }
      }
    }
  }
}
