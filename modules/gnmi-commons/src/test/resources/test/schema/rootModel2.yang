module root-model-2 {

  yang-version "1";

  namespace "tag:opendaylight.org.,2021:yang:test:v1:gnmi:converter:root2";

  prefix "rm2";

  organization "PANTHEONtech s.r.o";

  description
    "Test model for simple YANG structure";

  container root-container {
    description "Root testingcontainer";

    leaf element {
      type string;
    }

  }

}
