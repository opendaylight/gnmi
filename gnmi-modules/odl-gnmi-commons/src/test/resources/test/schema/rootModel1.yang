module root-model-1 {

  yang-version "1";

  namespace "tag:opendaylight.org.,2021:yang:test:v1:gnmi:converter:root1";

  prefix "rm1";

  organization "PANTHEONtech s.r.o";

  description
    "Test model for simple YANG structure";

  container root-container {
    description "Root testingcontainer";

    leaf-list elements {
      type string;
    }

  }

}
